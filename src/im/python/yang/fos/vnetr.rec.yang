module vnetr.rec {
    namespace "urn:fog05:im:fim:vnet";
    prefix "vnetr";

    typedef net_state {
        type enumeration {
            enum CREATE;
            enum CONNECT;
            enum DISCONNECT;
            enum DESTROY;
        }
    }

    typedef ip_kind {
        type enumeration {
            enum IPV4;
            enum IPV6;
        }
    }

    grouping address_information {

        leaf ip_version {
            type ip_kind;
        }

        leaf gateway {
            type string;
        }

        leaf dhcp_enable {
            type boolean;
        }

        leaf dhcp_range {
            type string;
        }

        leaf dns {
            type string;
        }
    }

    grouping record {
        leaf uuid {
            type string;
        }

        leaf status {
            type net_state;
        }

        leaf properites {
            type string;
        // should be json
        }

        container ip_configuration {
            uses address_information;
        }
    }

    container vnet_record {
        uses record;
    }
}
