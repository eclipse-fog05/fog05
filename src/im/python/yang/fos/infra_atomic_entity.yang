module infra_atomic_entity {
    namespace "urn:fog05:im:infra:atomicentity";
    prefix "atomicentityr";

    import infra_fdu {
        prefix "infra_fdu";
    }

    typedef cp_kind {
        type enumeration {
            enum VPORT;
        }
    }

    typedef vl_kind {
        type enumeration {
            enum ELINE;
            enum ELAN;
        }
    }

    typedef ip_kind {
        type enumeration {
            enum IPV4;
            enum IPV6;
        }
    }

    grouping address_information {

        leaf ip_version {
            type ip_kind;
        }

        leaf subnet {
            type string;
        }

        leaf gateway {
            type string;
        }

        leaf checksum {
            description
              "SHA1 checksum of the image file";
            type string;
        }

        leaf dhcp_enable {
            type boolean;
        }

        leaf dhcp_range {
            type string;
        }

        leaf-list dns {
            type string;
        }
    }
    grouping connection_point {

        leaf uuid {
            type string;
        }

        leaf cp_id {
            type string;
        }

        leaf cp_type {
            type cp_kind;
        }

        leaf port_security_enabled {
            type boolean;
        }

        leaf vld_ref {
            description
              "Reference to the VL this CP is connected";
            type string;
        }

        leaf veth_face_name {
            type string;
        }

        leaf br_name {
            type string;
        }

        leaf properties {
            type string;
        }

        leaf status {
            type string;
        }
    }

    grouping internal_virtual_link_record {
        leaf uuid {
            type string;
        }

        leaf internal_vl_id {
            type string;
        }

        leaf is_mgmt {
            type boolean;
        }

        leaf vl_type {
            type vl_kind;
        }

        leaf root_bandwidth {
            type int64;
        }

        leaf leaf_bandwidth {
            type int64;
        }

        leaf-list int_cps {
            type string;
        }

        container ip_configuration {
            uses address_information;
        }

        leaf overlay {
            type boolean;
        }

        leaf vni {
            type string;
        }

        leaf vlan_id {
            type string;
        }

        leaf face {
            type string;
        }
    }

    grouping record {
        leaf uuid {
            type string;
        }

        leaf atomic_entity_id {
            type string;
        }

        list fdus {
            key "uuid";
            uses infra_fdu:record;
        }

        list internal_virtual_links {
            key "uuid";
            uses internal_virtual_link_record;
        }

        list connection_points {
            key "uuid";
            uses connection_point;
        }

        leaf-list depends_on {
            type string;
        }
    }

    container ae_record {
        uses record;
    }
}
