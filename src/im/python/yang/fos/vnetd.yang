module vnetd {
    namespace "urn:fog05:im:fim:vnet";
    prefix "vnetd";

    typedef vn_type {
        type enumeration {
            enum ELINE;
            enum ELAN;
        }
    }

    typedef ip_kind {
        type enumeration {
            enum IPV4;
            enum IPV6;
        }
    }

    grouping address_information {

        leaf ip_version {
            type ip_kind;
        }

        leaf gateway {
            type string;
        }

        leaf dhcp_enable {
            type boolean;
        }

        leaf dhcp_range {
            type string;
        }

        leaf dns {
            type string;
        }
    }

    grouping descriptor {
        leaf uuid {
            description
              "UUID of the Virtual Link";
            type string;
        }

        leaf name {
            description
              "Unique name of the Virtual Link";
            type string;
        }

        leaf is_mgmt {
            description
              "True if this virtual link is used for management";
            type boolean;
        }

        leaf net_type {
            description
              "Type of the virtual link";
            type vn_type;
        }

        container ip_configuration {
            uses address_information;
        }
    }

    container vnet_descriptor {
        uses descriptor;
    }
}
