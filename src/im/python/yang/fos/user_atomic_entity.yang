module user_atomic_entity {
    namespace "urn:fog05:im:user:atomicentity";
    prefix "atomicentityd";

    import user_fdu {
        prefix "user_fdu";
    }

    typedef cp_kind {
        type enumeration {
            enum VPORT;
        }
    }

    typedef vl_kind {
        type enumeration {
            enum ELINE;
            enum ELAN;
        }
    }

    typedef ip_kind {
        type enumeration {
            enum IPV4;
            enum IPV6;
        }
    }

    grouping address_information {

        leaf ip_version {
            type ip_kind;
        }

        leaf subnet {
            type string;
        }

        leaf gateway {
            type string;
        }

        leaf checksum {
            description
              "SHA1 checksum of the image file";
            type string;
        }

        leaf dhcp_enable {
            type boolean;
        }

        leaf dhcp_range {
            type string;
        }

        leaf-list dns {
            type string;
        }
    }
    grouping connection_point {

        leaf uuid {
            type string;
        }

        leaf name {
            type string;
        }

        leaf id {
            type string;
        }

        leaf short_name {
            type string;
        }

        leaf cp_type {
            type cp_kind;
        }

        leaf port_security_enabled {
            type boolean;
        }

        leaf vld_ref {
            description
              "Reference to the VL this CP is connected";
            type string;
        }
    }

    grouping internal_virtual_link_descriptor {
        leaf id {
            type string;
        }

        leaf name {
            type string;
        }

        leaf is_mgmt {
            type boolean;
        }

        leaf short_name {
            type string;
        }

        leaf description {
            type string;
        }

        leaf vl_type {
            type vl_kind;
        }

        leaf root_bandwidth {
            type int64;
        }

        leaf leaf_bandwidth {
            type int64;
        }

        leaf-list int_cps {
            type string;
        }

        container ip_configuration {
            uses address_information;
        }
    }

    grouping descriptor {
        leaf uuid {
            type string;
        }

        leaf id {
            type string;
        }

        leaf name {
            type string;
        }

        leaf description {
            type string;
        }

        list fdus {
            key "id";
            uses user_fdu:descriptor;
        }

        list internal_virtual_links {
            key "id";
            uses internal_virtual_link_descriptor;
        }

        list connection_points {
            key "id";
            uses connection_point;
        }

        leaf-list depends_on {
            type string;
        }
    }

    container ae_descriptor {
        uses descriptor;
    }
}
