/*
 *
 *   Copyright 2018 ADLINK Technology Inc.
 *
 * See the NOTICE file(s) distributed with this work for additional
 * information regarding copyright ownership.
 *
 * This program and the accompanying materials are made available under the
 * terms of the Eclipse Public License 2.0 which is available at
 * http://www.eclipse.org/legal/epl-2.0, or the Apache License, Version 2.0
 * which is available at https://www.apache.org/licenses/LICENSE-2.0.
 *
 * SPDX-License-Identifier: EPL-2.0 OR Apache-2.0
 *
 * Contributors: Gabriele Baldoni, ADLINK Technology Inc. - MEAO Information Model
 *
 */

module appd-base {
    namespace "http://fog05.io/meapp/meao-1.0/appd-base";
    prefix "appd-base";

    import meao-types {
        prefix "meaotypes";
    }

    grouping appd-descriptor {

        leaf id {
            description
              "Identifier for the APPD";
            type string {
                length "1..63";
            }
        }

        leaf name {
            description
              "APPD Name";
            type string;
        }
        leaf vendor {
            description
              "APPD Vendor";
            type string;
        }

        leaf version {
            description
              "Version of the APPD";
            type string;
        }

        leaf soft-version {
            description
              "Version of the ME App Software";
            type string;
        }

        leaf-list mec-version {
            description
              "Version of MEC System Compatible with this ME App";
            type string;
            min-elements 1;
        }

        leaf description {
            description
              "Human readable description of the ME App";
            type string;
        }

        list service-required {

            description
              "Descrives services a me app require to run";
            key "ser-name";
            uses meaotypes:service-dependency;
        }

        list service-optional {
            description
              "Describe the service a ME app may use if present";
            key "ser-name";
            uses meaotypes:service-dependency;
        }

        list service-produced {
            description
              "Descrive the services an ME app is able to produce
               to the platform";
            key "id";
            leaf id {
                type string;
            }
            uses meaotypes:service-descriptor;
        }

        list feature-required {
            description
              "Describes the feature a ME app need to run";
            key "id";
            leaf id {
                type string;
            }
            uses meaotypes:feature-dependency;
        }

        list feature-optional {
            description
              "Describes the feature a ME app may use if available";
            key "id";
            leaf id {
                type string;
            }
            uses meaotypes:feature-dependency;
        }

        list transport-dependencies {
            description
              "Transports, in any, this applicatiom
               requires to be provided by the platform.
               These transport will be used by the platform 
               to deliver services provided by this application.
               Only relevar for ME app that produce services";
            key "id";
            leaf id {
                type string;
            }
            uses meaotypes:transport-dependency;
        }

        list traffic-rule {
            description
              "Describes the traffic rule the ME app requires";
            key "traffic-rule-id";
            uses meaotypes:traffic-rule-descriptor;
        }

        list dns-rule {
            description
              "Describes the DNS rules the ME app requires";
            key "dns-rule-id";
            uses meaotypes:dsn-rule-descriptor;
        }

        container latency {
            description
              "Describe the maximum latency tollerated by the ME app";
            uses meaotypes:latency-descriptor;
        }
    }
}
