/*
 *
 *   Copyright 2018 ADLINK Technology Inc.
 *
 * See the NOTICE file(s) distributed with this work for additional
 * information regarding copyright ownership.
 *
 * This program and the accompanying materials are made available under the
 * terms of the Eclipse Public License 2.0 which is available at
 * http://www.eclipse.org/legal/epl-2.0, or the Apache License, Version 2.0
 * which is available at https://www.apache.org/licenses/LICENSE-2.0.
 *
 * SPDX-License-Identifier: EPL-2.0 OR Apache-2.0
 *
 * Contributors: Gabriele Baldoni, ADLINK Technology Inc. - MEAO Information Model
 *
 */


 module appd {

    namespace "urn:fog05:params:xml:mec:yang:meao:descriptor:appd";
    prefix "appd-descriptor";

    import appd-base {
        prefix "appd-base";
    }

    container appd-descriptor {
        description
          "Mobile Edge Application Desciptor (AppD).";
        uses appd-base:appd-descriptor;
    }
   // THIS IS FOR DEMO PURPOSE ONLY
   leaf fos-descriptor {
        description
          "Eclipse fog05 normal descriptor";
        type string;
   }

}
