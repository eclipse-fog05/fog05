/*
 * 
 *   Copyright 2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module project-vnfd
{
  namespace "http://riftio.com/ns/riftware-1.0/project-vnfd";
  prefix "project-vnfd";

  import rw-project {
    prefix "rw-project";
  }

  import vnfd-base {
    prefix "vnfd-base";
  }

  revision 2017-02-28 {
    description
      "Initial revision. This YANG file defines
       the Virtual Network Function (VNF) descriptor
       under a project";
    reference
      "Derived from earlier versions of base YANG files";
  }

  augment /rw-project:project {
    container vnfd-catalog {
      description
        "Virtual Network Function Descriptor (VNFD).";

      list vnfd {
        key "id";

        uses vnfd-base:vnfd-descriptor;
      }
    }
  }
}

// vim: sw=2
